(defun dtr(x) (* (/ pi 180) x))
(command "osmode" "0") (command "cmdecho" "0") (setvar "filedia" 0)
(command "-layer" "m" "grid1" "c" "7" "" "m" "grid2" "c" "7" "" "m" "Profile1" "c" "1" "" "m" "text1" "c" "7" "" "")
(command "-layer" "m" "Profile2" "c" "3" "" "m" "Profile3" "c" "5" "" "m" "Profile4" "c" "6" "" "m" "text2" "c" "7" "" "")
(command "ltscale" "15") (setvar "filedia" 1) (setvar "dimzin" 2)
(command "-style" "section" "romant" "2.0" "" "" "" "" "")
;=============*==========*==========*===========*===============
(defun c:sf() 
	(initget 3) (setq hs(getreal "\n Hoz.Scale :") vs(getreal "\n Ver.Scale :")
				hsf(/ 1000 hs) vsf(/ 1000 vs) ) (princ)
)
;=============*==========*==========*===========*===============
(defun c:datum() 
		(if (and (not hs) (not vs))
		     (progn (alert "* Error * Sorry Try Again") (exit) )
		     (progn (initget 1) 
			    (setq dtm(getreal "\nEnter datum :")
				  dtm1(rtos dtm 2 3) dt_m(strcat "DATUM : " dtm1)
			    )
		     )
		)
		(princ)
)
;=============*==========*==========*===========*===============
(defun c:babu1() (c:datum) (setq dst "l" gl "l" bl "l"  fl "l" tl "l" glt(list 0)  xtt(list 0) 
			       blt(list 0)  flt(list 0) tlt(list 0) dtt(list 0) gtt(list 0) ttt(list 0)
			 ) 
	(while (and (/= gl "") (/= gl " "))
		(setq dst(getstring "\n Enter Distance :") 
				dst_(atof dst) dst1(rtos dst_ 2 0)
				xc(* dst_ hsf) xn(- xc 1)
				dtt(append dtt (list dst_)) xtt(append xtt (list xn))
		)
		(if (and (/= dst "") (/= dst " "))
		    (progn (setq gl(getstring "\n Enter Ground Level :")
		     		 bl(getstring "\n Enter Canal Bed Level :")
				 fl(getstring "\n Enter Design F.S.L :")
				 tl(getstring "\n Enter Design T.B.L :")
				 gl_(atof  gl)  bl_(atof bl)  fl_(atof fl) tl_(atof tl)
				 gl1(rtos gl_ 2 3) bl1(rtos bl_ 2 3) fl1(rtos fl_ 2 3) tl1(rtos tl_ 2 3)
				 gl2(- gl_ dtm) bl2(- bl_ dtm)  fl2(- fl_ dtm)  tl2(- tl_ dtm)
				 yg(* gl2 vsf)  yb(* bl2 vsf)  yf(* fl2 vsf) yt(* tl2 vsf)
				 pt1(list xc yg) pt2(list xc yb) pt3(list xc yf) pt4(list xc yt)
				 glt(append glt (list pt1)) blt(append blt (list pt2))  
				 flt(append flt (list pt3)) tlt(append tlt (list pt4))  
				 gtt(append gtt (list gl_)) ftt(append ftt (list tl_))  
				 gp1(list xc 0) gp2(list xc -125)  tp1(list xn -123) tp2(list xn -109)
				 tp3(list xn -99) tp4(list xn -84) tp5(list xn -69) 
				 tp6(list xn -54) tp7(list xn -39) tp8(list xn -24)
			   )
			   (command "-layer" "s" "text1" "" "") 
			   (progn
			       (if (or (> gl_ bl_) (> gl_ tl_)) (setq q1(- gl_ bl_) q1_(rtos q1 2 3)) (setq q1_ "0.00") )
				   (command "text" tp7 90 q1_)
			   ) 
			   (progn
			       (if (< gl_ tl_) (setq q2(- tl_ gl_) q2_(rtos q2 2 3) ) (setq q2_ "0.00") )  
				   (command "text" tp8 90 q2_)
		           )
			   
			   (command "-layer" "s" "text1" "" "") (command "text" tp1 90 dst1)
			   (command "-layer" "s" "profile1" "" "") (command "text" tp3 90 gl1)  
			   (command "-layer" "s" "profile2" "" "")	(command "text" tp4 90 bl1)
			   (command "-layer" "s" "profile3" "" "") (command "text" tp5 90 fl1)  
			   (command "-layer" "s" "profile4" "" "")(command "text" tp6 90 tl1)
			   (command "-layer" "s" "grid2" "lt" "hidden" "" "") 
			   ;(command "line" gp1 pt1 "")
		      )
		      (setq gl "" bl "" fl "" tl "")
		)
	)
		(setq glt(cdr glt)  blt(cdr blt)  flt(cdr flt) tlt(cdr tlt) n8 0 n9 1
			n1 0 n2 0 n3 0 n4 0  asclen(length glt)  dtt(cdr dtt) xtt(cdr xtt)
			glt1(append glt (list ""))  blt1(append blt (list ""))
		        flt1(append flt (list ""))  tlt1(append tlt (list "")) dln(- (length dtt) 2)
			mtt(append gtt ttt)
			
		)
		(repeat dln 
			(setq dt1(nth n8 dtt) dt2(nth n9 dtt) t_d1(- dt2 dt1) tdd(rtos t_d1 2 0)
		       	      x_t1(nth n8 xtt) x_t2(nth n9 xtt) xc1(/ (+ x_t1 x_t2) 2) tpp(list xc1 -105)
		              n8(1+ n8) n9(1+ n9)
			)
			(command "text" "j" "c" tpp 0 tdd)
		)
		
		(command "-layer" "s" "profile1" "" "")
		(command "pline")
		(repeat (+ 1 asclen) (setq pro_pt1(nth n1 glt1)  n1(1+ n1) )
			 (princ pro_pt1) (princ)
			(command pro_pt1 )  
		)
		(COMMAND "-CH" "L" "" "P" "LW" "1.0" "")

		(command "-layer" "s" "profile2" "" "")
		(command "pline")
		(repeat (+ 1 asclen) (setq pro_pt2(nth n2 blt1)  n2(1+ n2) )
			 (princ pro_pt1) (princ)
			(command pro_pt2 )  
		)
		(COMMAND "-CH" "L" "" "P" "LW" "1.0" "")

		(command "-layer" "s" "profile3" "" "")
		(command "pline")
		(repeat (+ 1 asclen) (setq pro_pt3(nth n3 flt1)  n3(1+ n3) )
			 (princ pro_pt3) (princ)
			(command pro_pt3 )  
		)
		(COMMAND "-CH" "L" "" "P" "LW" "1.0" "")

		(command "-layer" "s" "profile4" "" "")
		(command "pline")
		(repeat (+ 1 asclen) (setq pro_pt4(nth n4 tlt1)  n4(1+ n4) )
			 (princ pro_pt4) (princ)
			(command pro_pt4)  
		)
		(COMMAND "-CHAINGE" "L" "" "P" "LW" "1.0" "")

		(setq pts(nth 0 glt) pte(last glt) pt0(list (car pts) 0) px(- (car pts) 40)
		      qt1(list px 0) qt2(list (car pte) 0)  lp(polar pt0 pi 20) 
	      		qt3(polar qt1 (* (/ pi 2) 3) 125)  qt4(polar qt3 (/ pi 2) 15) qq(polar qt3 0 35)
	     		of1(list (car pts) -15) of2(list (car pts) -30) of3(list (car pts) -45)
	      		of4(list (car pts) -60)    tx1(- (car pts) 22) tt10(list tx1 -5)
	      		tt1(list tx1 1) tt2(list tx1 -17.5) tt3(list tx1 -32.5) pte2(list (car pte) -125)
	      		tt4(list tx1 -47.5)  tt5(list tx1 -62.5) tt6(list tx1 -77.5) 
	      		tt7(list tx1 -92.5)  tt8(list tx1 -105) tt9(list tx1 -119)
		)
		(command "-layer" "s" "grid1" "" "")  (command "line" qt1 qt2 "")
	(command "array" "l" "" "r" "2" "1" "-10") (command "array" "l" "" "r" "7" "1" "-15")
	(command "array" "l" "" "r" "2" "1" "-10")
	(command "offset" "15" qt4  qt3  "")
	(command "line" qt1 qt3 "")
	(command "-layer" "s" "text2" "" "") (command "text" "J" "C" tt1 0 dt_m)
	(command "text" "J" "C" tt2 0 "HEIGHT OF BANKING") (command "text" "J" "C" tt3 0 "DEPTH OF CUTTING")
	(command "text" "J" "C" tt8 0 "DISTANCE") (command "text" "J" "C" tt9 0 "CHAINAGE")
	(command "text" "J" "C" tt10 0 "VILLAGE LIMITS") (command "-layer" "s" "profile4" "" "")
	(command "text" "J" "C" tt4 0 "T.B.L") (command "-layer" "s" "profile3" "" "") (command "text" "J" "C" tt5 0 "F.S.L")
	(command "-layer" "s" "profile2" "" "")(command "text" "J" "C" tt6 0 "C.B.L") 
	(command "-layer" "s" "profile1" "" "")(command "text" "J" "C" tt7 0 "G.L")
	
	(setq k1(apply 'max mtt) df(- k1 dtm) k2(+ df 1) k(fix k2)  k6(* (+ k 0.5) vsf) qr(list (car qq) k6)
	      gap 10 f(/ gap vsf) t(fix (/ k f)) lv(+ dtm f) tt gap
	)
	(command "-layer" "s" "text1" "" "") 
	(SETQ W1 TT )
	(repeat t
		(setq rp(polar lp (/ pi 2) gap) lv1(rtos lv 2 3) lv2(strcat lv1 " ") W2(LIST -5 W1) W3(POLAR W2 PI 4))
		(command "text" rp  0 lv2)
		(COMMAND "LINE" W2 W3 "")
		(setq lv(+ lv f) gap(+ gap tt) W1(+ W1 TT) )
	)
	(command "line" qq qr "") (command "line" qt2 pte2 "") (command "zoom" "e")

	
)
